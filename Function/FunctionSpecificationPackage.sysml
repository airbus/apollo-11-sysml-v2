//
// Copyright (c) 2026 AIRBUS and its affiliates.
// This Source Code Form is subject to the terms of the Mozilla Public
// License, v. 2.0. If a copy of the MPL was not distributed with this
// file, You can obtain one at http://mozilla.org/MPL/2.0/.
//

package FunctionSpecificationPackage {
	
	private import FunctionalRequirementsPackage::*;
	private import FunctionsPackage::*;
	
	requirement performLunarMissionSpecification {
		doc /* Apollo 11 Function requirements group */
		subject performLunarMission : PerformLunarMission;

		requirement 'flr-R001' : PropellantLoadingRequirement;
		requirement 'flr-R002' : ConsumableConditioningRequirement;
		requirement 'flr-R003' : CrewIngressRequirement;
		requirement 'flr-R004' : CabinPressurizationRequirement;
		requirement 'flr-R005' : CountdownSequencingRequirement;
		requirement 'flr-R006' : CountdownAbortRequirement;
		requirement 'flr-R007' : Stage1ThrustInitiationRequirement;
		requirement 'flr-R008' : Stage1ThrustMagnitudeRequirement;
		requirement 'flr-R009' : Stage2ThrustInitiationRequirement;
		requirement 'flr-R010' : Stage2PropulsionRequirement;
		requirement 'flr-R011' : OrbitInsertionThrustInitiationRequirement;
		requirement 'flr-R012' : OrbitInsertionThrustTerminationRequirement;
		requirement 'flr-R013' : AscentGuidanceRequirement;
		requirement 'flr-R014' : AscentStagingCommandRequirement;
		requirement 'flr-R015' : CrewAscentMonitoringRequirement;
		requirement 'flr-R016' : CrewAscentAbortRequirement;
		requirement 'flr-R017' : GroundTelemetryAnalysisRequirement;
		requirement 'flr-R018' : GroundPerformanceVerificationRequirement;
		requirement 'flr-R019' : TliThrustInitiationRequirement;
		requirement 'flr-R020' : TliThrustControlRequirement;
		requirement 'flr-R021' : ModuleSeparationRequirement;
		requirement 'flr-R022' : ModuleRepositioningRequirement;
		requirement 'flr-R023' : ModuleConnectionRequirement;
		requirement 'flr-R024' : InSpacePropulsionRequirement;
		requirement 'flr-R025' : AttitudeControlRequirement;
		requirement 'flr-R026' : NavigationalDataAcquisitionRequirement;
		requirement 'flr-R027' : TrajectoryCalculationRequirement;
		requirement 'flr-R028' : CourseCorrectionCalculationRequirement;
		requirement 'flr-R029' : CourseCorrectionExecutionRequirement;
		requirement 'flr-R030' : CrewSystemMonitoringRequirement;
		requirement 'flr-R031' : GroundSystemMonitoringRequirement;
		requirement 'flr-R032' : SpacecraftDataTransmissionRequirement;
		requirement 'flr-R033' : SpacecraftDataReceptionRequirement;
		requirement 'flr-R034' : GroundTrackingRequirement;
		requirement 'flr-R035' : GroundCommunicationRelayRequirement;
		requirement 'flr-R036' : CrewActivitySchedulingRequirement;
		requirement 'flr-R037' : CrewRestProvisionRequirement;
		requirement 'flr-R038' : LoiThrustRequirement;
		requirement 'flr-R039' : LoiGuidanceRequirement;
		requirement 'flr-R040' : LanderSystemVerificationRequirement;
		requirement 'flr-R041' : LanderInterfaceVerificationRequirement;
		requirement 'flr-R042' : LanderCrewTransferRequirement;
		requirement 'flr-R043' : LanderConfigurationRequirement;
		requirement 'flr-R044' : ModuleDisengagementRequirement;
		requirement 'flr-R045' : ModuleSeparationManeuverRequirement;
		requirement 'flr-R046' : DescentPropulsionRequirement;
		requirement 'flr-R047' : DescentDataDisplayRequirement;
		requirement 'flr-R048' : DescentDataProcessingRequirement;
		requirement 'flr-R049' : ManualAttitudeControlRequirement;
		requirement 'flr-R050' : ManualPositionControlRequirement;
		requirement 'flr-R051' : PostLandingSafingRequirement;
		requirement 'flr-R052' : PostLandingVerificationRequirement;
		requirement 'flr-R053' : EgressPreparationRequirement;
		requirement 'flr-R054' : CabinDepressurizationRequirement;
		requirement 'flr-R055' : SurfaceMobilityRequirement;
		requirement 'flr-R056' : SymbolicDeploymentRequirement;
		requirement 'flr-R057' : SampleCollectionRequirement;
		requirement 'flr-R058' : SampleStorageRequirement;
		requirement 'flr-R059' : InstrumentDeploymentRequirement;
		requirement 'flr-R060' : VisualTransmissionRequirement;
		requirement 'flr-R061' : EvaIngressRequirement;
		requirement 'flr-R062' : CabinRepressurizationRequirement;
		requirement 'flr-R063' : SurfaceHabitationRequirement;
		requirement 'flr-R064' : SurfaceTimelineManagementRequirement;
		requirement 'flr-R065' : AscentThrustInitiationRequirement;
		requirement 'flr-R066' : AscentPropulsionRequirement;
		requirement 'flr-R067' : RendezvousCalculationRequirement;
		requirement 'flr-R068' : RendezvousExecutionRequirement;
		requirement 'flr-R069' : DockingApproachRequirement;
		requirement 'flr-R070' : DockingLatchingRequirement;
		requirement 'flr-R071' : IntervehicularCrewTransferRequirement;
		requirement 'flr-R072' : IntervehicularSampleTransferRequirement;
		requirement 'flr-R073' : AscentStageSeparationRequirement;
		requirement 'flr-R074' : AscentStageDisposalRequirement;
		requirement 'flr-R075' : TeiPropulsionRequirement;
		requirement 'flr-R076' : ReentryConfigurationRequirement;
		requirement 'flr-R077' : ServiceModuleJettisonRequirement;
		requirement 'flr-R078' : CleanSeparationRequirement;
		requirement 'flr-R079' : ReentryGuidanceRequirement;
		requirement 'flr-R080' : HeatDissipationRequirement;
		requirement 'flr-R081' : DeceleratorDeploymentRequirement;
		requirement 'flr-R082' : FinalVelocityRequirement;
		requirement 'flr-R083' : WaterLandingRequirement;
		requirement 'flr-R084' : PostLandingSystemsRequirement;
		requirement 'flr-R085' : CrewRecoveryRequirement;
		requirement 'flr-R086' : VesselTransferRequirement;
		requirement 'flr-R087' : QuarantineImplementationRequirement;
		requirement 'flr-R088' : QuarantineHabitationRequirement;
		requirement 'flr-R089' : SamplePreservationRequirement;
		requirement 'flr-R090' : SampleTransportRequirement;
		requirement 'flr-R091' : TGNCNavigationAccuracy;
		requirement 'flr-R092' : ManualPilotingLogic;
		requirement 'flr-R093' : SystemInterfaceCompatibility;
		requirement 'flr-R094' : TrainingSimulatorHours;
		requirement 'flr-R095' : CourseCorrectionCapability;
		requirement 'flr-R096' : SpacecraftOrientationControl;
		requirement 'flr-R097' : DescentDataAcquisition;
		requirement 'flr-R098' : LaunchVehicleAscentThrust;
		requirement 'flr-R099' : DescentRateModulation;
		requirement 'flr-R100' : ThermalProtectionLogic;
		requirement 'flr-R101' : TouchdownEnergyDissipation;
		requirement 'flr-R102' : AtmosphericScrubbingFunction;
		requirement 'flr-R103' : TelemetryStreamIntegrity;
		requirement 'flr-R104' : EMUPressureMaintenance;
		requirement 'flr-R105' : SoftwareMissionProficiency;
		requirement 'flr-R106' : SpaceEnvironmentResilience;
		requirement 'flr-R107' : VisualDataCapture;
		requirement 'flr-R108' : WasteContainmentFunction;
		requirement 'flr-R109' : CrossVehicleAudioLink;
		requirement 'flr-R110' : ComponentFaultTolerance;
		requirement 'flr-R111' : HumanMedicalSelfSufficiency;
		requirement 'flr-R112' : DataRedundancyArchiving;
		
		satisfy 'flr-R001' by performLunarMission.outbound.prep.load;
		satisfy 'flr-R002' by performLunarMission.outbound.prep.load;
		satisfy 'flr-R003' by performLunarMission.outbound.prep.board;
		satisfy 'flr-R004' by performLunarMission.outbound.prep.board;
		satisfy 'flr-R005' by performLunarMission.outbound.launch.countdown;
		satisfy 'flr-R006' by performLunarMission.outbound.launch.countdown;
		satisfy 'flr-R007' by performLunarMission.outbound.launch.provideThrust1;
		satisfy 'flr-R008' by performLunarMission.outbound.launch.provideThrust1;
		satisfy 'flr-R009' by performLunarMission.outbound.launch.provideThrust2;
		satisfy 'flr-R010' by performLunarMission.outbound.launch.provideThrust2;
		satisfy 'flr-R011' by performLunarMission.outbound.launch.provideThrust3;
		satisfy 'flr-R012' by performLunarMission.outbound.launch.provideThrust3;
		satisfy 'flr-R013' by performLunarMission.outbound.launch.guide;
		satisfy 'flr-R014' by performLunarMission.outbound.launch.guide;
		satisfy 'flr-R015' by performLunarMission.outbound.launch.observe;
		satisfy 'flr-R016' by performLunarMission.outbound.launch.observe;
		satisfy 'flr-R017' by performLunarMission.outbound.launch.analyze;
		satisfy 'flr-R018' by performLunarMission.outbound.launch.analyze;
		satisfy 'flr-R019' by performLunarMission.outbound.tli.burn;
		satisfy 'flr-R020' by performLunarMission.outbound.tli.control;
		satisfy 'flr-R021' by performLunarMission.outbound.tli.executeTransposition;
		satisfy 'flr-R022' by performLunarMission.outbound.tli.executeTransposition;
		satisfy 'flr-R023' by performLunarMission.outbound.tli.reconfigure;
		satisfy 'flr-R024' by performLunarMission.outbound.loi.burn;
		satisfy 'flr-R025' by performLunarMission.outbound.tli.provideAttitudeControlAndThrust;
		satisfy 'flr-R026' by performLunarMission.outbound.coast.trackAndRelay;
		satisfy 'flr-R027' by performLunarMission.outbound.coast.calculate;
		satisfy 'flr-R028' by performLunarMission.outbound.coast.calculate;
		satisfy 'flr-R029' by performLunarMission.outbound.coast.correct;
		satisfy 'flr-R030' by performLunarMission.outbound.coast.monitorOnboard;
		satisfy 'flr-R031' by performLunarMission.outbound.coast.monitorGround;
		satisfy 'flr-R032' by performLunarMission.outbound.coast.comms;
		satisfy 'flr-R033' by performLunarMission.outbound.coast.comms;
		satisfy 'flr-R034' by performLunarMission.outbound.coast.trackAndRelay;
		satisfy 'flr-R035' by performLunarMission.outbound.coast.trackAndRelay;
		satisfy 'flr-R036' by performLunarMission.outbound.coast.rest;
		satisfy 'flr-R037' by performLunarMission.outbound.coast.rest;
		satisfy 'flr-R038' by performLunarMission.outbound.loi.burn;
		satisfy 'flr-R039' by performLunarMission.outbound.loi.control;
		satisfy 'flr-R040' by performLunarMission.lunarOps.prepLanding.checkout;
		satisfy 'flr-R041' by performLunarMission.lunarOps.prepLanding.checkout;
		satisfy 'flr-R042' by performLunarMission.lunarOps.prepLanding.prep;
		satisfy 'flr-R043' by performLunarMission.lunarOps.prepLanding.prep;
		satisfy 'flr-R044' by performLunarMission.lunarOps.prepLanding.undock;
		satisfy 'flr-R045' by performLunarMission.lunarOps.prepLanding.undock;
		satisfy 'flr-R046' by performLunarMission.lunarOps.land.burn;
		satisfy 'flr-R047' by performLunarMission.lunarOps.land.monitor;
		satisfy 'flr-R048' by performLunarMission.lunarOps.land.monitor;
		satisfy 'flr-R049' by performLunarMission.lunarOps.land.pilot;
		satisfy 'flr-R050' by performLunarMission.lunarOps.land.pilot;
		satisfy 'flr-R051' by performLunarMission.lunarOps.explore.postLand;
		satisfy 'flr-R052' by performLunarMission.lunarOps.explore.postLand;
		satisfy 'flr-R053' by performLunarMission.lunarOps.explore.prepEva;
		satisfy 'flr-R054' by performLunarMission.lunarOps.explore.prepEva;
		satisfy 'flr-R055' by performLunarMission.lunarOps.explore.eva;
		satisfy 'flr-R056' by performLunarMission.lunarOps.explore.eva;
		satisfy 'flr-R057' by performLunarMission.lunarOps.explore.collect;
		satisfy 'flr-R058' by performLunarMission.lunarOps.explore.collect;
		satisfy 'flr-R059' by performLunarMission.lunarOps.explore.deploy;
		satisfy 'flr-R060' by performLunarMission.lunarOps.explore.deploy;
		satisfy 'flr-R061' by performLunarMission.lunarOps.explore.conclude;
		satisfy 'flr-R062' by performLunarMission.lunarOps.explore.conclude;
		satisfy 'flr-R063' by performLunarMission.lunarOps.explore.rest;
		satisfy 'flr-R064' by performLunarMission.lunarOps.explore.rest;
		satisfy 'flr-R065' by performLunarMission.lunarOps.ascendAndDock.ascend;
		satisfy 'flr-R066' by performLunarMission.lunarOps.ascendAndDock.ascend;
		satisfy 'flr-R067' by performLunarMission.lunarOps.ascendAndDock.calculate;
		satisfy 'flr-R068' by performLunarMission.lunarOps.ascendAndDock.rendezvous;
		satisfy 'flr-R069' by performLunarMission.lunarOps.ascendAndDock.dock;
		satisfy 'flr-R070' by performLunarMission.lunarOps.ascendAndDock.dock;
		satisfy 'flr-R071' by performLunarMission.lunarOps.ascendAndDock.transfer;
		satisfy 'flr-R072' by performLunarMission.lunarOps.ascendAndDock.transfer;
		satisfy 'flr-R073' by performLunarMission.lunarOps.ascendAndDock.jettison;
		satisfy 'flr-R074' by performLunarMission.lunarOps.ascendAndDock.jettison;
		satisfy 'flr-R075' by performLunarMission.returnJourney.tei.burn;
		satisfy 'flr-R076' by performLunarMission.returnJourney.coast.prep;
		satisfy 'flr-R077' by performLunarMission.returnJourney.land.separate;
		satisfy 'flr-R078' by performLunarMission.returnJourney.land.separate;
		satisfy 'flr-R079' by performLunarMission.returnJourney.land.guide;
		satisfy 'flr-R080' by performLunarMission.returnJourney.land.guide;
		satisfy 'flr-R081' by performLunarMission.returnJourney.land.deploy;
		satisfy 'flr-R082' by performLunarMission.returnJourney.land.deploy;
		satisfy 'flr-R083' by performLunarMission.returnJourney.land.splashdown;
		satisfy 'flr-R084' by performLunarMission.returnJourney.land.splashdown;
		satisfy 'flr-R085' by performLunarMission.returnJourney.recover.retrieve;
		satisfy 'flr-R086' by performLunarMission.returnJourney.recover.retrieve;
		satisfy 'flr-R087' by performLunarMission.returnJourney.recover.quarantine;
		satisfy 'flr-R088' by performLunarMission.returnJourney.recover.quarantine;
		satisfy 'flr-R089' by performLunarMission.returnJourney.recover.secure;
		satisfy 'flr-R090' by performLunarMission.returnJourney.recover.secure;
		satisfy 'flr-R091' by performLunarMission.outbound.coast.trackAndRelay;
		satisfy 'flr-R092' by performLunarMission.lunarOps.land.pilot;
		satisfy 'flr-R093' by performLunarMission.outbound.prep.load;
		satisfy 'flr-R094' by performLunarMission.outbound.prep.board;
		satisfy 'flr-R095' by performLunarMission.outbound.coast.correct;
		satisfy 'flr-R096' by performLunarMission.outbound.tli.provideAttitudeControlAndThrust;
		satisfy 'flr-R097' by performLunarMission.lunarOps.land.monitor;
		satisfy 'flr-R098' by performLunarMission.outbound.launch.provideThrust1;
		satisfy 'flr-R099' by performLunarMission.lunarOps.land.burn;
		satisfy 'flr-R100' by performLunarMission.returnJourney.land.guide;
		satisfy 'flr-R101' by performLunarMission.lunarOps.land.burn;
		satisfy 'flr-R102' by performLunarMission.outbound.coast.monitorOnboard;
		satisfy 'flr-R103' by performLunarMission.outbound.coast.comms;
		satisfy 'flr-R104' by performLunarMission.lunarOps.explore.eva;
		satisfy 'flr-R105' by performLunarMission.outbound.launch.guide;
		satisfy 'flr-R106' by performLunarMission.outbound.coast.monitorOnboard;
		satisfy 'flr-R107' by performLunarMission.lunarOps.explore.deploy;
		satisfy 'flr-R108' by performLunarMission.outbound.coast.monitorOnboard;
		satisfy 'flr-R109' by performLunarMission.lunarOps.explore.eva;
		satisfy 'flr-R110' by performLunarMission.outbound.loi.burn;
		satisfy 'flr-R111' by performLunarMission.outbound.coast.rest;
		satisfy 'flr-R112' by performLunarMission.returnJourney.recover.retrieve;		
	}
}
